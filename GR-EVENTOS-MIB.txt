GR-EVENTOS-MIB DEFINITIONS ::= BEGIN

IMPORTS
	enterprises,
	MODULE-IDENTITY,
	OBJECT-TYPE,
	Counter32,
	TimeTicks
		FROM SNMPv2-SMI
	OBJECT-GROUP
		FROM SNMPv2-CONF;

eventosMIB MODULE-IDENTITY
	LAST-UPDATED "202102201414Z"	-- Feb 20, 2021, 2:14:00 PM
	ORGANIZATION ""
	CONTACT-INFO
		""
	DESCRIPTION
		"MIB para monitorização de datas para
		eventos."
	REVISION "202102201414Z"	-- Feb 20, 2021, 2:14:00 PM
	DESCRIPTION
		"Initial version."
	-- 1.3.6.1.4.1.8888
	::= { enterprises 8888 }


numeroEventos OBJECT-TYPE
	SYNTAX  Counter32
	MAX-ACCESS read-only
	STATUS  current
	DESCRIPTION
		"Numero de eventos na MIB."
	-- 1.3.6.1.4.1.8888.1
	::= { eventosMIB 1 }


eventosTable OBJECT-TYPE
	SYNTAX  SEQUENCE OF EventoEntry
	MAX-ACCESS not-accessible
	STATUS  current
	DESCRIPTION
		"Tabela que armazena todos os eventos."
	-- 1.3.6.1.4.1.8888.2
	::= { eventosMIB 2 }


eventoEntry OBJECT-TYPE
	SYNTAX  EventoEntry
	MAX-ACCESS not-accessible
	STATUS  current
	DESCRIPTION
		"Entrada para a tabela de eventos."
	INDEX {
		eventoIndex }
	-- 1.3.6.1.4.1.8888.2.1
	::= { eventosTable 1 }


EventoEntry ::= SEQUENCE {

	eventoIndex         Counter32,
	eventoName          OCTET STRING,
	eventoEstado        INTEGER,
	eventoTempoAnos     INTEGER,
	eventoTempoMeses    INTEGER,
	eventoTempoSemanas  INTEGER,
	eventoTempoDias     INTEGER,
	eventoTempoHoras    INTEGER,
	eventoTempoMinutos  INTEGER,
	eventoDuracao       TimeTicks,
	eventoFrasePassado  OCTET STRING,
	eventoFrasePresente OCTET STRING,
	eventoFraseFuturo   OCTET STRING }


eventoIndex OBJECT-TYPE
	SYNTAX  Counter32
	MAX-ACCESS read-only
	STATUS  current
	DESCRIPTION
		"Identificador do evento."
	-- 1.3.6.1.4.1.8888.2.1.1
	::= { eventoEntry 1 }


eventoName OBJECT-TYPE
	SYNTAX  OCTET STRING
	MAX-ACCESS read-only
	STATUS  current
	DESCRIPTION
		"Nome do evento."
	-- 1.3.6.1.4.1.8888.2.1.2
	::= { eventoEntry 2 }


eventoEstado OBJECT-TYPE
	SYNTAX  INTEGER
	MAX-ACCESS read-only
	STATUS  current
	DESCRIPTION
		"Estado atual do evento.
		(0) Futuro
		(1) Presente
		(2) Passado"
	-- 1.3.6.1.4.1.8888.2.1.3
	::= { eventoEntry 3 }


eventoTempoAnos OBJECT-TYPE
	SYNTAX  INTEGER
	MAX-ACCESS read-only
	STATUS  current
	DESCRIPTION
		"Tempo que falta para o evento ou, caso seja no passado, há quanto tempo foi o evento.
		Só a parte referente aos anos."
	-- 1.3.6.1.4.1.8888.2.1.4
	::= { eventoEntry 4 }


eventoTempoMeses OBJECT-TYPE
	SYNTAX  INTEGER
	MAX-ACCESS read-only
	STATUS  current
	DESCRIPTION
		"Tempo que falta para o evento ou, caso seja no passado, há quanto tempo foi o evento.
		Só a parte referente aos meses."
	-- 1.3.6.1.4.1.8888.2.1.5
	::= { eventoEntry 5 }


eventoTempoSemanas OBJECT-TYPE
	SYNTAX  INTEGER
	MAX-ACCESS read-only
	STATUS  current
	DESCRIPTION
		"Tempo que falta para o evento ou, caso seja no passado, há quanto tempo foi o evento.
		So a parte referente as semanas."
	-- 1.3.6.1.4.1.8888.2.1.6
	::= { eventoEntry 6 }


eventoTempoDias OBJECT-TYPE
	SYNTAX  INTEGER
	MAX-ACCESS read-only
	STATUS  current
	DESCRIPTION
		"Tempo que falta para o evento ou, caso seja no passado, há quanto tempo foi o evento.
		Só a parte referente aos dias."
	-- 1.3.6.1.4.1.8888.2.1.7
	::= { eventoEntry 7 }


eventoTempoHoras OBJECT-TYPE
	SYNTAX  INTEGER
	MAX-ACCESS read-only
	STATUS  current
	DESCRIPTION
		""
	-- 1.3.6.1.4.1.8888.2.1.8
	::= { eventoEntry 8 }


eventoTempoMinutos OBJECT-TYPE
	SYNTAX  INTEGER
	MAX-ACCESS read-only
	STATUS  current
	DESCRIPTION
		"Tempo que falta para o evento ou, caso seja no passado, há quanto tempo foi o evento.
		Só a parte referente aos minutos."
	-- 1.3.6.1.4.1.8888.2.1.9
	::= { eventoEntry 9 }


eventoDuracao OBJECT-TYPE
	SYNTAX  TimeTicks
	MAX-ACCESS read-only
	STATUS  current
	DESCRIPTION
		"Duração do evento."
	-- 1.3.6.1.4.1.8888.2.1.10
	::= { eventoEntry 10 }


eventoFrasePassado OBJECT-TYPE
	SYNTAX  OCTET STRING
	MAX-ACCESS read-only
	STATUS  current
	DESCRIPTION
		"Frase para descrever o evento no passado."
	-- 1.3.6.1.4.1.8888.2.1.11
	::= { eventoEntry 11 }


eventoFrasePresente OBJECT-TYPE
	SYNTAX  OCTET STRING
	MAX-ACCESS read-only
	STATUS  current
	DESCRIPTION
		"Frase para descrever o evento no presente."
	-- 1.3.6.1.4.1.8888.2.1.12
	::= { eventoEntry 12 }


eventoFraseFuturo OBJECT-TYPE
	SYNTAX  OCTET STRING
	MAX-ACCESS read-only
	STATUS  current
	DESCRIPTION
		"Frase para descrever o evento no futuro."
	-- 1.3.6.1.4.1.8888.2.1.13
	::= { eventoEntry 13 }


-- Conformance
--

grMIBConf OBJECT IDENTIFIER 
	-- 1.3.6.1.4.1.8888.3
	::= { eventosMIB 3 }

-- Groups
--

grMIBGroups OBJECT IDENTIFIER 
	-- 1.3.6.1.4.1.8888.3.1
	::= { grMIBConf 1 }

-- Compliances
--

grMIBCompliances OBJECT IDENTIFIER 
	-- 1.3.6.1.4.1.8888.3.2
	::= { grMIBConf 2 }

grMIBBasicGroup OBJECT-GROUP
	OBJECTS {
		numeroEventos,
		eventoIndex,
		eventoName,
		eventoEstado,
		eventoTempoAnos,
		eventoFrasePassado,
		eventoFrasePresente,
		eventoFraseFuturo,
		eventoDuracao,
		eventoTempoDias,
		eventoTempoHoras,
		eventoTempoMinutos,
		eventoTempoMeses,
		eventoTempoSemanas }
	STATUS  current
	DESCRIPTION
		"Basic objects."
	-- 1.3.6.1.4.1.8888.3.1.1 --
	-- 1.3.6.1.4.1.8888.3.1.1
	::= { grMIBGroups 1 }

END
